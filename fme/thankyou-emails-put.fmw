FME workspace thankyou-emails-put.fmw

Readers:
- JSON_1: JSON from put.json

Writers:
- MSSQL_ADO_1: MSSQL_ADO to ThankYou

JSONFeature (reader JSON_1)
    attributes: Col string, ID int, Val string
    -> Logger
Logger
    MESSAGE = Feature is:
    MAXFEATS = 20
    MAXCOORDS = 20
    LOGGED -> TestFilter
TestFilter
    TEST_LIST = BOOL_OP,OR,COMPOSITE_TEST,<Unused>,TEST_CLAUSE,"TEST @Value(Col) = Gift",Gift,BOOL_OP,OR,COMPOSITE_TEST,<Unused>,TEST_CLAUSE,"TEST @Value(Col) = Giver",Giver,BOOL_OP,OR,COMPOSITE_TEST,<Unused>,TEST_CLAUSE,"TEST @Value(Col) = EmailAddress",EmailAddress,BOOL_OP,OR,COMPOSITE_TEST,<Unused>,TEST_CLAUSE,"TEST @Value(Col) = EmailNote",EmailNote
    DEFAULT_VALUE = <UNFILTERED>
    Gift -> AttributeRenamer
    Giver -> AttributeRenamer_2
    EmailAddress -> AttributeRenamer_3
    EmailNote -> AttributeRenamer_4
AttributeRenamer
    ATTR_TABLE = RENAME_SET_DEFAULT Val > Gift
    -> dbo.ThankYouEmail (writer MSSQL_ADO_1)
AttributeRenamer_2
    ATTR_TABLE = RENAME_SET_DEFAULT Val > Giver
    -> dbo.ThankYouEmail (writer MSSQL_ADO_1)
AttributeRenamer_3
    ATTR_TABLE = RENAME_SET_DEFAULT Val > EmailAddress
    -> dbo.ThankYouEmail (writer MSSQL_ADO_1)
AttributeRenamer_4
    ATTR_TABLE = RENAME_SET_DEFAULT Val > EmailNote
    -> dbo.ThankYouEmail (writer MSSQL_ADO_1)
dbo.ThankYouEmail (writer MSSQL_ADO_1)
    attributes: ID identity, Gift varchar(50), Giver varchar(50), EmailAddress varchar(50), EmailNote text
